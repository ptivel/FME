FME workspace RasterClip.fmw

Parameters:
- State = Maine
- SourceDataset_SHAPE = $(FME_MF_DIR)index\CountiesTifIDs.shp   # Source Esri Shape File(s)
- Orig_DRG = C:/GCT/FME_World_Tour_2015/Raster_Download_Clip_Mosaic/Maine_DRGs   # Where do you want to store the original DRGs?
- SourceDataset_GEOTIFF = $(Tifs)   # Source GeoTIFF File(s)
- DestDataset_GEOTIFF = $(MosaicState)   # Destination GeoTIFF Directory
- DestDataset_GEOTIFF_4 = $(Clipped_Counties)   # Destination GeoTIFF Directory
- Tifs:   # Python Script
      #Author: Phil Tivel
      #Created: 11/19/2014
      #Python Version 2.75
      #This script is meant to be used in FME. It it goes into the http://libremap.org/ website, finds and downloads all
      #desired DRG topo maps for a state. Once the files are downloaded the script creates and returns long string of
      #the tiff file paths that can be utilized in the tif Source Parameters of an FME workspace.
      #This script should be set in the Private Parameters of an FME workspace.
      
      #importing program functionality
      import urllib2,urllib,re,os
      sName = str(FME_MacroValues['State'])
      stateName = sName.lower()
      tifDir = str(FME_MacroValues['Orig_DRG'])
      #Accesing the http://libremap.org website
      response = urllib2.urlopen('http://libremap.org/data/state/'+stateName+'/drg/')
      html = response.read()
      
      #Declaring Variables
      
      fpathsString = ""
      #tifPath = "C:\\GCT\\Donna\\Rhode_Island_DSG\\"
      uniqueUrls = []
      uniqueTifPath = []
      
      #variable replaces everything with tfw in the website with tiff
      urlFix = html.replace("tfw","tif")
      
      #variable replaces everything with fgd in the website with tiff
      urlFix2 = urlFix.replace("fgd","tif")
      
      #Utilizing Regular Expressions. Variable stores a list of URLs in the website that start with http:// and end with .tif. Thus creating a
      #list of URLs for the each downloadable tif on the page.
      myUrls = re.findall(r"http://.*?.tif",urlFix2)
      
      #for loop to crate a unique URLs list since some of the URLs became duplicates when I replaced tfw and fgd with tif
      #to aid in the regular expression search abouve
      for item in myUrls:
          if item not in uniqueUrls:
              uniqueUrls.append(item)
      
      #for loop to try and download each tif found on the website. It tries to download it and if it fails then it
      #removes it from the list and moves to the next tif.
      for item in uniqueUrls:
          tifName = os.path.basename(item)
      
          try:
              #Downloading tif data
              urllib.urlretrieve(item,tifDir+'/'+tifName)
      
              #building separate file path list to be used once files are downloaded to the users computer
              uniqueTifPath.append(tifDir +'/'+ tifName)
          except:
              item + " was not a good tiff"
              #removing failed downloads from the url list
              uniqueUrls.remove(item)
      
      #building string of tif file paths to be returned and used in the FME Source Paramters
      for item in uniqueTifPath:
          fpathsString = fpathsString + '"' + item + '"' + " "
      
      #Creating final tif path string that will be utilized in FME. This removes the final comma from the string
      tifString = '"'+fpathsString[0:-1] + '"'
      
      print "total files done: " + str(len(uniqueUrls))
      
      #This return only works when this script is incorporated into FME.
      #It ruturns a the string of tiff file paths in the form of "tiff1,tiff2,tiff3,etc"
      #which then gets used in the tif source parameters of the FME model
      return tifString
- MosaicState:   # Python Script
      orig = str(FME_MacroValues['Orig_DRG'])
      
      state = orig + "_Mosaic_State_GCSWGS84"
      
      return state
- Clipped_Counties:   # Python Script
      orig = str(FME_MacroValues['Orig_DRG'])
      clipped = orig + "_Clipped_CountyGCSWGS84"
      
      return clipped

Readers:
- GEOTIFF_1: GEOTIFF from $(SourceDataset_GEOTIFF)
- SHAPE_1: SHAPE from $(SourceDataset_SHAPE)

Writers:
- GEOTIFF_2: GEOTIFF to $(DestDataset_GEOTIFF)
- GEOTIFF_3: GEOTIFF to $(DestDataset_GEOTIFF_4)

Note: Tifs that are automatically derived and input as a source / dataset based on which state the user chooses at the / start of the model.
GEOTIFF (reader GEOTIFF_1)
    -> Reprojector
Note: Reprojecting Rasters to GCSWGS84
Reprojector
    INTERPOLATION_TYPE_NAME = Nearest Neighbor
    DEST = LL-WGS84
    SOURCE = Read from feature
    STROKE_ARCS = Yes
    RASTER_CELL_SIZE = Preserve Cells
    REPROJECTED -> Clipper [input 2]
Note: Layer containing the US State, County, and Grid ID information
CountiesTifIDs (reader SHAPE_1)
    attributes: COUNTY_NAM char(32), QUAD_QD_ID char(100), STATE_NAME char(35)
    -> Dissolver
    -> Dissolver_2
Note: Dissolving layer at the Grid ID level
Dissolver
    ACCUM_INPUT_ATTRS = Yes
    GROUP_BY = QUAD_QD_ID
    NO_OVRLP = No
    AREA -> Tester_3
Note: Testing for user chosen state name
Tester_3
    TEST_CLAUSE = TEST @Value(STATE_NAME) LIKE $(State)
    TEST_MODE = Automatic
    TEST_DESCRIPTION = ""
    BOOL_OP = OR
    PASSED -> Clipper [input 1]
Note: Clipping each input raster to the topoq24 grid
Clipper
    MERGE_ATTRS = Yes
    BOUNDARY_CASES = Treat as Inside
    CLIP_TYPE = Multiple Clippers
    ATTR_PREFIX = clipper_
    CLIPPED_ATTR = _clipped
    PRESERVE_CLIPPEE_EXTENTS = No
    CREATE_AGGREGATES = Yes
    INSIDE -> SubstringExtractor
Note: Fining and discarding clipped raster edge pieces
SubstringExtractor
    RESULT_ATTR = ID1
    START = -2
    END = -1
    SRC_ATTR = fme_basename
    -> StringCaseChanger
StringCaseChanger
    CHANGE_TYPE = UPPERCASE
    ATTRLIST = ID1
    ATTRCHOICE = Selected Attributes
    -> SubstringExtractor_2
SubstringExtractor_2
    RESULT_ATTR = ID2
    START = -2
    END = -1
    SRC_ATTR = clipper_QUAD_QD_ID
    -> StringCaseChanger_2
StringCaseChanger_2
    CHANGE_TYPE = lowercase
    ATTRLIST = ID1 ID2
    ATTRCHOICE = Selected Attributes
    -> Tester
Tester
    TEST_CLAUSE = TEST @Value(ID1) = @Value(ID2)
    TEST_MODE = Automatic
    TEST_DESCRIPTION = ""
    BOOL_OP = OR
    PASSED -> RasterMosaicker
Note: Mosaicing all the Rasters at the state level
RasterMosaicker
    SNAPPING_TYPE_NAME = Resample
    ACCUM_ATTRS_NAME = Yes
    INTERPOLATION_TYPE_NAME = Nearest Neighbor
    COMPOSITE_USING_ALPHA_BAND_NAME = No
    MERGE_PALETTES_NAME = Yes
    NODATA_OVERWRITE = No
    -> Clipper_2 [input 2]
    -> NewFeatureType (writer GEOTIFF_2)
Note: Outputing Mosiaced State Tif
NewFeatureType (writer GEOTIFF_2)
Note: Dissolving layer at the County level
Dissolver_2
    ACCUM_INPUT_ATTRS = Yes
    GROUP_BY = COUNTY_NAM
    NO_OVRLP = No
    AREA -> Tester_2
Tester_2
    TEST_CLAUSE = TEST @Value(STATE_NAME) LIKE $(State)
    TEST_MODE = Automatic
    TEST_DESCRIPTION = ""
    BOOL_OP = OR
    PASSED -> Clipper_2 [input 1]
Note: Clipping the Mosaiced raster to the county level
Clipper_2
    MERGE_ATTRS = Yes
    BOUNDARY_CASES = Treat as Inside
    CLIP_TYPE = Multiple Clippers
    ATTR_PREFIX = clipper_
    CLIPPED_ATTR = _clipped
    PRESERVE_CLIPPEE_EXTENTS = No
    CREATE_AGGREGATES = Yes
    INSIDE -> NewFeatureType (writer GEOTIFF_3)
Note: Outputing County Mosaiced and Clipped Tifs
NewFeatureType (writer GEOTIFF_3)
