FME workspace Language_Evaluator.fmw

Parameters:
- Sentiment_File = C:/GCT/FME_World_Tour_2015/Language_Evaluator/Sentiment.xlsx   # Source Microsoft Excel File(s)
- DestDataset_XLSXW2_6 = $(FME_MF_DIR)Content_Stats.xlsx   # Destination Microsoft Excel File
- SourceDataset_XLSXR = $(FME_MF_DIR)Content.xlsx   # Source Microsoft Excel File(s)
- Create_exp:   # Python Script
      import xlrd
      import fmeobjects
      import fme
      
      path = fme.macroValues['Sentiment_File']#FME_MacroValues['expfile']
      print path
      mydata = xlrd.open_workbook(path)
      
      worksheet = mydata.sheet_by_name('Sheet1')
      num_rows = worksheet.nrows - 1
      curr_row = -1
      expression = ''
      
      while curr_row < num_rows:
          curr_row += 1
          row = worksheet.row(curr_row)
          expression = expression + " " + str(row[0]) + 'OR|'
          #expression = expression + str(row[0]) + 'OR|'
      
      exp1 = expression.replace("text:u'","")
      exp2 = exp1.replace("'","")
      exp3 = exp2.replace("(","\(")
      exp4 = exp3.replace(")","\)")
      exp5 = exp4.replace("*","\*")
      exp6 = exp5.replace("?","\?")
      exp7 = exp6.replace("^","\^")
      exp8 = exp7.replace(".","\.")
      exp9 = exp8.replace("|","\|")
      exp10 = exp9.replace("OR\|","|")
      exp11 = exp10.replace("$","\$")
      exp12 = exp11.replace("{","\{")
      exp13 = exp12.replace("}","\}")
      exp14 = exp13.replace("[","\[")
      exp15 = exp14.replace("]","\]")
      finalExp = exp15[:-1]
      
      print finalExp
      return finalExp
- exp = $(Create_exp)   # this is the expression

Readers:
- XLSXR_1: XLSXR from $(Sentiment_File)
- XLSXR_2: XLSXR from $(SourceDataset_XLSXR)

Writers:
- XLSXW2_1: XLSXW2 to $(DestDataset_XLSXW2_6)

Note: Original Input Data
Sheet1 (reader XLSXR_2)
    attributes: Content char(141)
    -> AttributeCreator
Note: Creating an attribute called "List Counter" / to be used in a later transformer to index a list.
AttributeCreator
    ATTR_LIST = list_counter,0
    -> StringLengthCalculator
Note: Calculating the length of the content field. / Needed for the Content Looper
StringLengthCalculator
    LENGTH_ATTR = _length
    SRC_ATTR = Content
    -> AttributeCreator_2
Note: Creating a counter to be used to track / iterations in the Content Looper loop.
AttributeCreator_2
    ATTR_LIST = ContentCounter,0
    -> AttributeCreator_3
Note: Creating the new attribute that will hold the characters in the content field / separated by a space. they need to be separated by a space so a list can be / made out of the characters and run in the Lister Loop.
AttributeCreator_3
    ATTR_LIST = Content_Spacer,""
    -> AttributeCreator_5
Note: Creating CodeAll variable so it can be used in Content Loop
AttributeCreator_5
    ATTR_LIST = CodeAll,""
    -> AttributeCreator_4
Note: Creating Languageall variable to be used in Content Loop
AttributeCreator_4
    ATTR_LIST = LanguageAll,""
    -> Content_Looper
    -> FeatureMerger_2 [input 2]
Note: Custom transformer to loop through and accumulate the languages of each character
Content_Looper: Content Loop
    -> AttributeSplitter
Note: Add all Languages from the LanguageAll field to a list
AttributeSplitter
    DROP_EMPTY_PARTS = Yes
    ATTR_NAME = LanguageAll
    DELIMITER = " "
    LIST_NAME = LanguageList
    TRIM_OPTION = Both
    -> AttributeSplitter_2
Note: Add all codes from the CodeAll field to a list
AttributeSplitter_2
    DROP_EMPTY_PARTS = Yes
    ATTR_NAME = CodeAll
    DELIMITER = " "
    LIST_NAME = CodeList
    TRIM_OPTION = Both
    -> ListHistogrammer_2
Note: Creates a list of statistical attributes associated / with the languages used for row of data. This includes / a list of languages used that does not repeat the language / multiple times. It also includes a list of the frequency a / given language is used.
Note: Concatenates the list of languages (different character codes) derived / from the numberical character codes in the Lister Loop.
ListHistogrammer_2
    SRC_LIST = CodeList{}
    LIST_NAME = _histogramcode
    -> ListHistogrammer
Note: Creates a list of statistical attributes associated / with the languages used for row of data. This includes / a list of languages used that does not repeat the language / multiple times. It also includes a list of the frequency a / given language is used.
ListHistogrammer
    SRC_LIST = LanguageList{}
    LIST_NAME = _histogram
    -> ListConcatenator_4
Note: Concatenates the list of languages that are unique values / created from the ListHistogrammer. This is shown in the final / output under the "Languages" field
ListConcatenator_4
    DROP_EMPTY_PARTS = No
    LIST_ATTR = _histogram{}.value
    SEP = "; "
    VAL_ATTR = Languages
    -> ListConcatenator_2
Note: Concatenates the list of languages that are unique values / created from the ListHistogrammer. This is shown in the final / output under the "Languages" field
ListConcatenator_2
    DROP_EMPTY_PARTS = No
    LIST_ATTR = _histogramcode{}.value
    SEP = "; "
    VAL_ATTR = CharacterCodes
    -> ListConcatenator_5
Note: Concatenates the lists showing the frequency of / languages being used for a single row of data. / The results can be seen in the Language_Frequency / field of the final data.
ListConcatenator_5
    DROP_EMPTY_PARTS = No
    LIST_ATTR = _histogram{}.count
    SEP = "; "
    VAL_ATTR = Language_Frequency
    -> FeatureMerger_2 [input 1]
FeatureMerger_2
    SUPPLIERS_FIRST = No
    ATTR_ACCUM_MODE = Merge Supplier
    ATTR_CONFLICT_RES = Use Requestor
    PROCESS_DUPS = No
    JOIN_KEYS = @Value(list_counter) @Value(list_counter) AUTO
    MERGE_TYPE = Attributes Only
    MERGED -> PythonCaller
Note: Final Output Data. It resembles the input data, except has two added / fields that help determine the multi-lingual characteristics of the data.
PythonCaller
    NEW_ATTRIBUTES = LanguageGrouping LanguageType PossibleEmoteChar EmoticonDetection
    PYTHONSOURCE:
      #This script is does and returns several things. It finds if something is multi lingual or a sinlge language, as well if it is a possibe emoticon that isnt in emoticon excel file.
      #In addtion it performs a varaeity of statistics on the content of the data. If the Languages are "AAAAAAABBBBCDEEEEEEAAAAA" the script formats it as 7A 4B 1C 1D 6E 5A. This helps
      #determine if it is multi lingual and gives another usefull statistic of the data.
      import fmeobjects, re
      def LanguageGroup(feature):

          #Def function that will checks if all things in the list are the same language
          def all_same(items):
              return all(x == items[0] for x in items)
          #Represents the LanguageAll field that contains the language of each character code
          languageString = feature.getAttribute("LanguageAll")
          contentString = feature.getAttribute("Content")
          contentList = list(contentString)
          #Creating a list from the LanguageAll field string using a space as the delimiter
          languageList = languageString.split(" ")

          #Setting up counters and empty variables to be used shortly
          groupCounter = 1
          loopCounter = 0
          pattern = ""
          patternList =[]
          patternList2 =[]


          for group in languageList:

              try:
                  #Checking if the next item in the list is the same item as the current item, if so then
                  #the count of that language type is increased.
                  if languageList[loopCounter+1] == group:
                      groupCounter += 1
                      loopCounter += 1
                  #If the next item in the Language list is not the same as the current item then a new language
                  #group with a reset counter is started
                  else:
                      groupcount = str(groupCounter) + "(" + group + ")"
                      pattern = pattern + " " + groupcount
                      patternList.append(groupCounter)
                      patternList2.append(group)
                      groupCounter = 1
                      loopCounter += 1

              #This except occurs when the try statement above runs into the end of the list and can't check
              #what's after the last item in the list.
              except:
                  groupcount = str(groupCounter) + "(" + group + ")"
                  pattern = pattern + " " + groupcount
                  #patfin represents the language and the group count eg. [5(Arabic), 3(Basic_Latin), 8(Arabic)]
                  patfin = pattern[5:-3]
                  patternList.append(groupCounter)
                  patternList2.append(group)

          #patlistgc represents just the number in patfin eg. [5,3,8] This will be what allows us to find
          #single vs multiple languages in the content and later possible emoticons
          patlistgc = patternList[1:-1]
          #patlistg represents just the language in patfin eg. [Arabic,Basic_Latin, Arabic]
          patlistg = patternList2[1:-1]
          #Changing palistgc to string to aid in the search of emoticons [5,3,8] will now appear as 5_3_8
          #we are doing this to find the pattern 1_1_1 which will identify a possible emoticon

          indexpos = 0
          possemotechar=''
          ltype = ''
          possemote = ''
          for group in patlistgc:
              try:
                  if patlistgc[indexpos] == 1 and patlistgc[indexpos+1] == 1 and patlistgc[indexpos+2] == 1 and patlistg[indexpos] != "Ignore_Character" and patlistg[indexpos+1] != "Ignore_Character"and patlistg[indexpos+2] != "Ignore_Character":

                      contentpos = 0
                      for x in patlistgc[0:indexpos]:
                          contentpos = contentpos + x
                      indexpos+=1
                      possemotechar = possemotechar + contentList[contentpos] + contentList[contentpos+1] + contentList[contentpos+2] + '    '
                      possemote = "Possible Emoticon"

                  else:
                      indexpos += 1
              except:
                  break

          #We don't want special characters like a space, period, octothorp, etc to count towards something being
          #multiple languages or a possilbe emoticon. The below code causes these characters to be ignored in this
          #type of consideration. We are sssuming emoticons that use these symbols are caught in the
          #input emoticon file in the FME model.
          indexpos = 0

          for group in patlistg:
              if group == "Ignore_Character":

                  patlistg.remove(group)
                  del(patlistgc[indexpos])
                  indexpos += 1

              else:
                  indexpos += 1

          contentpos = 0
          for item in languageList:

              try:
                  if item == "Ignore_Character":
                      del(contentList[contentpos])

                  else:
                      contentpos+=1
              except:
                  break


          #Checking to see if content is single or multi language using def function all_same() created at the start
          for group in patlistg:

              if all_same(patlistg) == True:
                  ltype = "Single Language"
              else:
                  ltype = "Multi Language"



          feature.setAttribute("LanguageGrouping", patfin)
          feature.setAttribute("LanguageType", ltype)
          feature.setAttribute("PossibleEmoteChar", possemotechar)
          feature.setAttribute("EmoticonDetection", possemote)
    PYTHONSYMBOL = LanguageGroup
    -> StringSearcher
StringSearcher
    CASE = no
    MATCHED_PARTS_ATTR = _matched_parts
    STRING_TO_SEARCH = @Value(Content)
    REGEXP = $(exp)
    MATCHED_RESULT_ATTR = EmoticonMatch
    MATCHED -> AttributeCreator_6
    NOT_MATCHED -> AttributeFilter
AttributeCreator_6
    ATTR_LIST = EmoticonDetection,Detected Emoticon
    -> AttributeFilter
AttributeFilter
    ATTR_NAME = LanguageType
    ATTR_VALUES = <EMPTY>,Multi Language,Single Language,<MISSING>,<NULL>,<UNFILTERED>
    Multi Language -> Sheet1 (writer XLSXW2_1)
    Single Language -> Sheet1 (writer XLSXW2_1)
Sheet1 (writer XLSXW2_1)
    attributes: Content auto(20,format_type;Simple;font_type;;font_color;;fill_color;;custom_options;;text_wrap;no), LanguageGrouping auto(20,format_type;Simple;font_type;;font_color;;fill_color;;custom_options;;text_wrap;no), LanguageType auto(20,format_type;Simple;font_type;;font_color;;fill_color;;custom_options;;text_wrap;no), Languages auto(20,format_type;Simple;font_type;;font_color;;fill_color;;custom_options;;text_wrap;no), Language_Frequency auto(20,format_type;Simple;font_type;;font_color;;fill_color;;custom_options;;text_wrap;no), EmoticonDetection auto(20,format_type;Simple;font_type;;font_color;;fill_color;;custom_options;;text_wrap;no), EmoticonMatch auto(20,format_type;Simple;font_type;;font_color;;fill_color;;custom_options;;text_wrap;no), PossibleEmoteChar auto(20,format_type;Simple;font_type;;font_color;;fill_color;;custom_options;;text_wrap;no)

FME custom transformer Histogram_List_Concatenator

INPUT (input)
    -> ListElementCounter
ListElementCounter
    CNT_ATTR = Histogram_count
    LIST_NAME = _histogram{}
    -> ListIndexer
ListIndexer
    LIST_ATTR = _histogram{}
    INDEX = @Value(Histogram_count)
    -> StringConcatenator
StringConcatenator
    VAL_ATTR = _concatenated2
    PARM_LINE = @Value(value)@Value(count)
    -> AttributeCreator
AttributeCreator
    ATTR_LIST = list_counter2,@Evaluate(@Value(list_counter2)+1)
    -> Tester_2
Tester_2
    TEST_CLAUSE = TEST @Value(list_counter2) = @Value(Histogram_count)
    TEST_MODE = Automatic
    BOOL_OP = OR
    TEST_DESCRIPTION = ""
    FAILED -> INPUT (output)
    PASSED -> OUTPUT (output)
    FAILED -> OUTPUT (output)
OUTPUT (output)
INPUT (output)

FME custom transformer Content Loop

INPUT (input)
    -> SubstringExtractor
Note: Looking at one character in the content field / each time through the loop
SubstringExtractor
    START = @Value(ContentCounter)
    END = @Value(ContentCounter)
    RESULT_ATTR = _substring
    SRC_ATTR = Content
    -> CharacterCodeExtractor
Note: Creates many different ranges of numbers that corelate / to a different character code.
CharacterCodeExtractor
    SRC_ATTR = _substring
    CODE_ATTR = _code
    -> AttributeFilter
Note: Filters out Farsi characters. Wil be replaced with a tester at a later time
AttributeFilter
    ATTR_NAME = _code
    ATTR_VALUES = <BLANK>,<UNFILTERED>,1740,9771,64511,1662,1670,1688,1711
    1740 -> AttributeCreator_5
    9771 -> AttributeCreator_5
    64511 -> AttributeCreator_5
    1670 -> AttributeCreator_5
    1662 -> AttributeCreator_5
    1688 -> AttributeCreator_5
    1711 -> AttributeCreator_5
    <BLANK> -> AttributeRangeMapper
    <UNFILTERED> -> AttributeRangeMapper
Note: Creates many different ranges of numbers that corelate / to a different character code.
AttributeRangeMapper
    IN_ATTR = _code
    OUT_ATTR = Language
    LUT = 1536,1791,Arabic,128,255,Latin-1_Supplement,256,383,Latin Extended-A,384,591,Latin Extended-B,19968,40959,Chinese_Japanese_Korean_Unified_Ideographs,1024,1279,Cyrillic,592,687,IPA_Extensions,688,767,Spacing_Modifier_Letters,768,879,Combining_Diacritical_Marks,880,1023,Greek,1328,1423,Armenian,1424,1535,Hebrew,1792,1871,Syriac,1920,1983,Thaana,2304,2431,Devanagari,2432,2559,Bengali,2560,2687,Gurmukhi,2688,2815,Gujarati,2816,2943,Oriya,2944,3071,Tamil,3072,3199,Telugu,3200,3327,Kannada,3328,3455,Malayalam,3456,3583,Sinhala,3584,3711,Thai,3712,3839,Lao,3840,4095,Tibetan,4096,4255,Myanmar,4256,4351,Georgian,4352,4607,Hangul_Jamo,4608,4991,Ethiopic,5024,5119,Cherokee,5120,5759,Unified_Canadian_Aboriginal_Syllabics,5760,5791,Ogham,5792,5887,Runic,6016,6143,Khmer,6144,6319,Mongolian,7680,7935,Latin_Extended_Additional,7936,8191,Greek_Extended,8192,8303,General_Punctuation,8304,8351,Superscripts_and_Subscripts,8352,8399,Currency_Symbols,8400,8447,Combining_Marks_for_Symbols,8448,8527,Letterlike_Symbols,8528,8591,Number_Forms,8592,8703,Arrows,8704,8959,Mathematical_Operators,8960,9215,Miscellaneous_Technical,9216,9279,Control_Pictures,9280,9311,Optical_Character_Recognition,9312,9471,Enclosed_Alphanumerics,9472,9599,Box_Drawing,9600,9631,Block_Elements,9632,9727,Geometric_Shapes,9728,9983,Miscellaneous_Symbols,9984,10175,Dingbats,10240,10495,Braille_Patterns,11904,12031,CJK_Radicals_Supplement,12032,12255,Kangxi_Radicals,12272,12287,Ideographic_Description_Characters,12288,12351,CJK_Symbols_and_Punctuation,12352,12447,Hiragana,12448,12543,Katakana,12544,12591,Bopomofo,12592,12687,Hangul_Compatibility_Jamo,12688,12703,Kanbun,12704,12735,Bopomofo_Extended,12800,13055,Enclosed_CJK_Letters_and_Months,13056,13311,CJK_Compatibility,13312,19893,CJK_Unified_Ideographs_Extension_A,40960,42127,Yi_Syllables,42128,42191,Yi_Radicals,44032,55203,Hangul_Syllables,55296,56191,High_Surrogates,56192,56319,High_Private_Use_Surrogates,56320,57343,Low_Surrogates,57344,63743,Private_Use,63744,64255,CJK_Compatibility_Ideographs,64256,64335,Alphabetic_Presentation_Forms,64336,65023,Arabic_Presentation_Forms-A,65056,65071,Combining_Half_Marks,65072,65103,CJK_Compatibility_Forms,65104,65135,Small_Form_Variants,65136,65278,Arabic_Presentation_Forms-B,65279,65279,Specials,65280,65519,Halfwidth_and_Fullwidth_Forms,65520,65533,Specials,32,47,Ignore_Character,58,64,Ignore_Character,91,96,Ignore_Character,123,127,Ignore_Character,0,31,Basic_Latin,48,57,Basic_Latin,65,90,Basic_Latin,97,122,Basic_Latin,,,
    -> Tester_2
Note: Checks for speical characters like punctuation so they are not identified as a language
Tester_2
    TEST_CLAUSE = TEST @Value(Language) = Special_Character
    TEST_MODE = Automatic
    BOOL_OP = OR
    TEST_DESCRIPTION = ""
    FAILED -> AttributeCreator_3
    PASSED -> AttributeCreator_3
Note: Setting language to Farsi for Farsi characters
AttributeCreator_5
    ATTR_LIST = Language,Farsi
    -> AttributeCreator_3
Note: Concatenating all language values from all characters into one field
AttributeCreator_3
    ATTR_LIST = LanguageAll,@Value(LanguageAll) @Value(Language)
    -> AttributeCreator_4
Note: Concatenating all code values from all characters into one field
AttributeCreator_4
    ATTR_LIST = CodeAll,@Value(CodeAll) @Value(_code)
    -> Tester
Note: Tester to continue the loop until all characters / have been looked through
Tester
    TEST_CLAUSE = NUM_TEST @Value(ContentCounter) < @Value(_length)
    TEST_MODE = Automatic
    BOOL_OP = OR
    TEST_DESCRIPTION = ""
    PASSED -> AttributeCreator
    FAILED -> OUTPUT (output)
Note: Incrementing the counter to stop the loop if it hits the length of the content field
AttributeCreator
    ATTR_LIST = ContentCounter,@Evaluate(@Value(ContentCounter)+1)
    -> INPUT (output)
INPUT (output)
OUTPUT (output)

FME custom transformer f

INPUT (input)
OUTPUT (output)

FME custom transformer Lister Loop

Note: Entry point for data into the List Looper
INPUT (input)
    -> ListElementCounter
Note: Counts the number of elements in each list / created from the "Content" field.
ListElementCounter
    CNT_ATTR = _element_count
    LIST_NAME = _list{}
    -> ListIndexer
Note: Uses the List Counter created at the start of the model / to index each position in the list. List Counter starts at 0 / and increments one each time through the loop.
ListIndexer
    LIST_ATTR = _list{}
    INDEX = @Value(list_counter)
    -> CharacterCodeExtractor
Note: Extracts the numerical character code of the first letter / of each element in the "Content" list.
CharacterCodeExtractor
    SRC_ATTR = _list
    CODE_ATTR = _code
    -> AttributeRangeMapper
Note: Creates many different ranges of numbers that corelate / to a different character code.
AttributeRangeMapper
    IN_ATTR = _code
    OUT_ATTR = Language
    LUT = 0,127,Basic_Latin,1536,1791,Arabic,128,255,Latin-1 Supplement,256,383,Latin Extended-A,384,591,Latin Extended-B,19968,40959,Chinese_Japanese_Korean_Unified_Ideographs,1024,1279,Cyrillic,592,687,IPA Extensions,688,767,Spacing Modifier Letters,768,879,Combining Diacritical Marks,880,1023,Greek,1328,1423,Armenian,1424,1535,Hebrew,1792,1871,Syriac,1920,1983,Thaana,2304,2431,Devanagari,2432,2559,Bengali,2560,2687,Gurmukhi,2688,2815,Gujarati,2816,2943,Oriya,2944,3071,Tamil,3072,3199,Telugu,3200,3327,Kannada,3328,3455,Malayalam,3456,3583,Sinhala,3584,3711,Thai,3712,3839,Lao,3840,4095,Tibetan,4096,4255,Myanmar,4256,4351,Georgian,4352,4607,Hangul Jamo,4608,4991,Ethiopic,5024,5119,Cherokee,5120,5759,Unified Canadian Aboriginal Syllabics,5760,5791,Ogham,5792,5887,Runic,6016,6143,Khmer,6144,6319,Mongolian,7680,7935,Latin Extended Additional,7936,8191,Greek Extended,8192,8303,General Punctuation,8304,8351,Superscripts and Subscripts,8352,8399,Currency Symbols,8400,8447,Combining Marks for Symbols,8448,8527,Letterlike Symbols,8528,8591,Number Forms,8592,8703,Arrows,8704,8959,Mathematical Operators,8960,9215,Miscellaneous Technical,9216,9279,Control Pictures,9280,9311,Optical Character Recognition,9312,9471,Enclosed Alphanumerics,9472,9599,Box Drawing,9600,9631,Block Elements,9632,9727,Geometric Shapes,9728,9983,Miscellaneous Symbols,9984,10175,Dingbats,10240,10495,Braille Patterns,11904,12031,CJK Radicals Supplement,12032,12255,Kangxi Radicals,12272,12287,Ideographic Description Characters,12288,12351,CJK Symbols and Punctuation,12352,12447,Hiragana,12448,12543,Katakana,12544,12591,Bopomofo,12592,12687,Hangul Compatibility Jamo,12688,12703,Kanbun,12704,12735,Bopomofo Extended,12800,13055,Enclosed CJK Letters and Months,13056,13311,CJK Compatibility,13312,19893,CJK Unified Ideographs Extension A,40960,42127,Yi Syllables,42128,42191,Yi Radicals,44032,55203,Hangul Syllables,55296,56191,High Surrogates,56192,56319,High Private Use Surrogates,56320,57343,Low Surrogates,57344,63743,Private Use,63744,64255,CJK Compatibility Ideographs,64256,64335,Alphabetic Presentation Forms,64336,65023,Arabic Presentation Forms-A,65056,65071,Combining Half Marks,65072,65103,CJK Compatibility Forms,65104,65135,Small Form Variants,65136,65278,Arabic Presentation Forms-B,65279,65279,Specials,65280,65519,Halfwidth and Fullwidth Forms,65520,65533,Specials,1740,1740,Farsi,9771,9771,Farsi,64508,64511,Farsi,1662,1662,Farsi,1670,1670,Farsi,1688,1688,Farsi,1711,1711,Farsi,,,
    -> AttributeCreator
Note: Increments the list counter by 1 / so that the next time through the / loop the next element in the / "Content" list is indexed.
AttributeCreator
    ATTR_LIST = list_counter,@Evaluate(@Value(list_counter)+1)
    -> Tester
Note: If the incremented list counter equals the total / number of elements in the list, then the loop ends / and output is sent out of the list looper. If it is less / than the elements in the list then it does another loop.
Tester
    TEST_CLAUSE = TEST @Value(list_counter) = @Value(_element_count)
    TEST_MODE = Automatic
    BOOL_OP = OR
    TEST_DESCRIPTION = ""
    FAILED -> INPUT (output)
    PASSED -> OUTPUT (output)
    FAILED -> OUTPUT (output)
Note: Output out of the Lister Loop if the tester / conditions are met
OUTPUT (output)
Note: Loops back to the Lister Loop input if the tester / conditions are not met.
INPUT (output)
