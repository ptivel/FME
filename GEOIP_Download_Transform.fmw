FME workspace GEOIP_Download_Transform.fmw

Parameters:
- Location:   # Python Script
      import requests,urllib2,urllib,re,os,zipfile,shutil
      from requests import session
      
      login_url1 = 'https://www.maxmind.com/en/member'
      login_url2 = 'https://www.maxmind.com/en/download_files'
      fileDir = 'C:/GEOIP'
      
      if not os.path.exists(fileDir):
          os.makedirs(fileDir)
      else:
          shutil.rmtree(fileDir)
          os.makedirs(fileDir)
      
      payload = {'action':'login','login':'usernamehere','password':'passwordhere','pkit_login':'1','pkit_done':r'https://www.maxmind.com/en/account'}
      
      with session() as c:
          c.post(login_url1, data=payload)
          request = c.get(login_url2)
          webpage = request.text
      
      
      myUrls = re.findall(r"https://download.maxmind.com/app/geoip_download.edition_id=174.*?.>|https://download.maxmind.com/app/geoip_download.edition_id=144.*?.>|https://download.maxmind.com/app/geoip_download.edition_id=178.*?.>|https://download.maxmind.com/app/geoip_download.edition_id=172.*?.>",webpage)
      for item in myUrls:
          print item[:-2]
      
          try:
              #Downloading Maxmind Data
              filePath = fileDir+'/'+item[59:62]+'.zip'
      
              urllib.urlretrieve(item[:-2],filePath)
      
      
              fh = open(filePath, 'rb')
              z = zipfile.ZipFile(fh)
              for name in z.namelist():
                  #extract only csv files
                  if name[-3:] == 'csv':
                      print name
                      outpath = fileDir
                      z.extract(name, outpath)
              fh.close()
              os.remove(filePath)
      
          except:
              item + " was not a good file"
      
      csvlist = []
      
      for root, dirs, files in os.walk(fileDir):
          for item in files:
              if item[-3:] =="csv":
                  csvlist.append(root+'\\'+item)
      
      #use in FME if I can incorporate [144Location,144ISP,172speed,174domain,178net]
      for item in csvlist:
          if item[-12:] =='Location.csv':
              location = item
          elif item[-11:] =='Org-144.csv':
              org = item
          elif item[-9:] == 'Speed.csv':
              speed = item
          elif item[-10:] == 'Domain.csv':
              domain = item
          elif item[-13:] == 'SpeedCell.csv':
              speedcell = item
          else:
              print "uh oh, something went wrong assigning parameters"
      
      location = '/'.join(location.split('\\'))
      
      return location
- Domain:   # Python Script
      import os
      
      fileDir = 'C:/GEOIP'
      
      csvlist = []
      
      for root, dirs, files in os.walk(fileDir):
          for item in files:
              if item[-3:] =="csv":
                  csvlist.append(root+'\\'+item)
          #print root
          #print files
      
      #use in FME if I can incorporate [144Location,144ISP,172speed,174domain,178net]
      for item in csvlist:
          if item[-12:] =='Location.csv':
              location = item
          elif item[-11:] =='Org-144.csv':
              org = item
          elif item[-9:] == 'Speed.csv':
              speed = item
          elif item[-10:] == 'Domain.csv':
              domain = item
          elif item[-13:] == 'SpeedCell.csv':
              speedcell = item
          else:
              print "uh oh, something went wrong assigning parameters"
      
      
      domain = '/'.join(domain.split('\\'))
      
      return domain
- SpeedCell:   # Python Script
      import os
      
      fileDir = 'C:/GEOIP'
      
      
      csvlist = []
      
      for root, dirs, files in os.walk(fileDir):
          for item in files:
              if item[-3:] =="csv":
                  csvlist.append(root+'\\'+item)
      
      #use in FME if I can incorporate [144Location,144ISP,172speed,174domain,178net]
      for item in csvlist:
          if item[-12:] =='Location.csv':
              location = item
          elif item[-11:] =='Org-144.csv':
              org = item
          elif item[-9:] == 'Speed.csv':
              speed = item
          elif item[-10:] == 'Domain.csv':
              domain = item
          elif item[-13:] == 'SpeedCell.csv':
              speedcell = item
          else:
              print "uh oh, something went wrong assigning parameters"
      
      
      speedcell = '/'.join(speedcell.split('\\'))
      
      return speedcell
- Org:   # Python Script
      import os
      
      fileDir = 'C:/GEOIP'
      
      csvlist = []
      
      for root, dirs, files in os.walk(fileDir):
          for item in files:
              if item[-3:] =="csv":
                  csvlist.append(root+'\\'+item)
      
      #use in FME if I can incorporate [144Location,144ISP,172speed,174domain,178net]
      for item in csvlist:
          if item[-12:] =='Location.csv':
              location = item
          elif item[-11:] =='Org-144.csv':
              org = item
          elif item[-9:] == 'Speed.csv':
              speed = item
          elif item[-10:] == 'Domain.csv':
              domain = item
          elif item[-13:] == 'SpeedCell.csv':
              speedcell = item
          else:
              print "uh oh, something went wrong assigning parameters"
      
      org = '/'.join(org.split('\\'))
      
      return org
- Speed:   # Python Script
      import os
      
      fileDir = 'C:/GEOIP'
      
      csvlist = []
      
      for root, dirs, files in os.walk(fileDir):
          for item in files:
              if item[-3:] =="csv":
                  csvlist.append(root+'\\'+item)
      
      #use in FME if I can incorporate [144Location,144ISP,172speed,174domain,178net]
      for item in csvlist:
          if item[-12:] =='Location.csv':
              location = item
          elif item[-11:] =='Org-144.csv':
              org = item
          elif item[-9:] == 'Speed.csv':
              speed = item
          elif item[-10:] == 'Domain.csv':
              domain = item
          elif item[-13:] == 'SpeedCell.csv':
              speedcell = item
          else:
              print "uh oh, something went wrong assigning parameters"
      
      speed = '/'.join(speed.split('\\'))
      
      return speed
- 144Loc = $(Location)   # Input 144 Loc File
- 172_Speed = $(Speed)   # Input 172 Speed File
- 144_ISP = $(Org)   # Input 144 ISP File
- 174_Domain = $(Domain)   # Input 174 Domain File
- 178_Net = $(SpeedCell)   # Input 178 Net Speed File
- DestDataset_CSV = C:\GEOIP   # Destination CSV (CommaSeparatedValue) Folder

Readers:
- CSV_1: CSV from $(144Loc)
- CSV_2: CSV from $(144_ISP)
- CSV_3: CSV from $(174_Domain)
- CSV_4: CSV from $(178_Net)
- CSV_5: CSV from $(172_Speed)

Writers:
- CSV_6: CSV to $(DestDataset_CSV)

Note: CSV: GeoIPCityISPOrg-144 [CSV]
CSV (reader CSV_2)
    attributes: startIpNum number(9,0), endIpNum number(9,0), locId number(7,0), ISP char(51), organization char(51)
    -> AttributeRenamer_4
AttributeRenamer_4
    ATTR_LIST = organization,org,""
    -> FeatureMerger [input 1]
Note: CSV: GeoIPCity-144-Location [CSV]
CSV (reader CSV_1)
    attributes: locId number(6,0), country char(3), region char(3), city char(27), postalCode char(7), latitude number(8,4), longitude number(9,4), metroCode number(4,0), areaCode number(4,0)
    -> FeatureMerger [input 2]
FeatureMerger
    SUPPLIER_PREFIX_DUMMY = YES
    SUPPLIERS_FIRST = No
    PROCESS_DUPS = No
    MERGE_TYPE = Attributes Only
    IGNORE_NULLS = Yes
    JOIN_KEYS = @Value(locId) @Value(locId) AUTO
    MERGED -> FeatureMerger_2 [input 1]
Note: CSV: GeoIPDomain [CSV]
CSV (reader CSV_3)
    attributes: col0 number(10,0), col1 number(10,0), col2 char(36)
    -> AttributeRenamer
AttributeRenamer
    ATTR_LIST = col0,startIpNum,"",col1,endIpNum,"",col2,domain,""
    -> FeatureMerger_2 [input 2]
Note: CSV: GeoIPNetSpeedCell [CSV]
CSV (reader CSV_4)
    attributes: col0 number(10,0), col1 number(10,0), col2 char(15), col3 char(15), col4 char(10)
    -> AttributeRenamer_2
AttributeRenamer_2
    ATTR_LIST = col0,startIpNum,"",col1,endIpNum,"",col4,connection,""
    -> FeatureMerger_2 [input 2]
Note: CSV: GeoIPSpeed [CSV]
CSV (reader CSV_5)
    attributes: col0 number(10,0), col1 number(10,0), col2 char(5)
    -> AttributeRenamer_3
AttributeRenamer_3
    ATTR_LIST = col0,startIpNum,"",col1,endIpNum,"",col2,speed,""
    -> FeatureMerger_2 [input 2]
FeatureMerger_2
    SUPPLIER_PREFIX_DUMMY = YES
    SUPPLIERS_FIRST = No
    PROCESS_DUPS = No
    MERGE_TYPE = Attributes Only
    IGNORE_NULLS = Yes
    JOIN_KEYS = @Value(startIpNum) @Value(startIpNum) AUTO
    MERGED -> PythonCaller
    NOT_MERGED -> PythonCaller
PythonCaller
    PYTHONSOURCE:
      import fmeobjects
      def ipMath(feature):
          start = feature.getAttribute("startIpNum")
          ipnum = int(start)


          o1 = int( ipnum / 16777216 ) % 256
          o2 = int( ipnum / 65536    ) % 256
          o3 = int( ipnum / 256      ) % 256
          o4 = int( ipnum            ) % 256

          address = ( str(o1) + '.', str(o2)+ '.', str(o3)+ '.', str(o4) )

          ipAddress = address[0] + address[1] + address[2] + address[3]
          feature.setAttribute("startIpAdd", ipAddress)

          end = feature.getAttribute("endIpNum")
          ipnum2 = int(end)

          p1 = int( ipnum2 / 16777216 ) % 256
          p2 = int( ipnum2 / 65536    ) % 256
          p3 = int( ipnum2 / 256      ) % 256
          p4 = int( ipnum2            ) % 256

          address2 = ( str(p1) + '.', str(p2)+ '.', str(p3)+ '.', str(p4) )

          ipAddress2 = address2[0] + address2[1] + address2[2] + address2[3]
          feature.setAttribute("endIpAdd", ipAddress2)
    PYTHONSYMBOL = ipMath
    NEW_ATTRIBUTES = startIpAdd endIpAdd
    -> GEOIP_Complete (writer CSV_6)
GEOIP_Complete (writer CSV_6)
    attributes: locId number(31,15), country char(3), region char(3), city char(27), postalCode char(7), metroCode number(31,15), areaCode number(31,15), startIpNum char(50), endIpNum char(50), startIpAdd char(50), endIpAdd char(50), latitude number(31,15), longitude number(31,15), ISP char(50), org char(50), domain char(50), connection char(50), speed char(50)
