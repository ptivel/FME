FME workspace GeoNames_Validator.fmw

Parameters:
- DestDataset_FILEGDB = $(FME_MF_DIR)Iran\Possible_GeoNames_Errors_Iran.gdb   # Destination Geodatabase
- SourceDataset_CSV = $(FME_MF_DIR)Iran\ir.txt   # Source CSV (CommaSeparatedValue) File(s)

Readers:
- CSV_1: CSV from $(SourceDataset_CSV) in LL-WGS84

Writers:
- FILEGDB_1: FILEGDB to $(DestDataset_FILEGDB)

CSV (reader CSV_1)
    attributes: RC number(2,0), UFI number(9,0), UNI number(9,0), LAT number(9,6), LONG number(9,6), DMS_LAT number(7,0), DMS_LONG number(7,0), MGRS char(16), JOG char(8), FC char(2), DSG char(5), PC char(1), CC1 char(9), ADM1 number(3,0), POP char(1), ELEV char(1), CC2 char(3), NT char(3), LC char(4), SHORT_FORM char(1), GENERIC char(22), SORT_NAME_RO char(51), FULL_NAME_RO char(55), FULL_NAME_ND_RO char(55), SORT_NAME_RG char(51), FULL_NAME_RG char(55), FULL_NAME_ND_RG char(55), NOTE char(1), MODIFY_DATE char(11), DISPLAY char(18),
      NAME_RANK number(2,0), NAME_LINK number(9,0), TRANSL_CD char(1), NM_MODIFY_DATE char(11)
    -> VertexCreator
    -> ListBuilder
VertexCreator
    MODE_NAME = Add Point
    XVAL = @Value(LONG)
    YVAL = @Value(LAT)
    -> Matcher_7
    -> Tester_6

Bookmark: Possible Generic Errors
  Provides statistics on the Generics used which can be used to help identify errors in the generic field. Output is a table that needs to be evaluated rather than spatial data. Only lists UFI number if the Generic is used less than 10 times for a DSG.
ListBuilder
    LIST_NAME = _list
    GRP_BY = DSG GENERIC
    -> ListHistogrammer
ListHistogrammer
    SRC_LIST = _list{}.GENERIC
    LIST_NAME = _histogram
    -> ListConcatenator
ListConcatenator
    LIST_ATTR = _histogram{}.count
    VAL_ATTR = Generic_Count
    DROP_EMPTY_PARTS = No
    SEP = ,
    -> Tester_13
Tester_13
    TEST_CLAUSE = TEST @Value(Generic_Count) < 10
    TEST_MODE = Automatic
    TEST_DESCRIPTION = ""
    BOOL_OP = OR
    PASSED -> ListConcatenator_2
    FAILED -> Tester_14
ListConcatenator_2
    LIST_ATTR = _list{}.UFI
    VAL_ATTR = UFIs
    DROP_EMPTY_PARTS = No
    SEP = ,
    -> Tester_14
Tester_14
    TEST_CLAUSE = TEST @Value(GENERIC) = ""
    TEST_MODE = Automatic
    TEST_DESCRIPTION = ""
    BOOL_OP = OR
    FAILED -> Generic_Statistics (writer FILEGDB_1)
Generic_Statistics (writer FILEGDB_1)
    attributes: GENERIC text(100), DSG text(100), Generic_Count int, UFIs text(100)

Bookmark: Multiple N Name Error
  If a UFI has multiple Native Names and the CC1 and CC2 attributes don't differentiate them and if they are not ADM features, then they are identified and saved as a medium risk error.
Note: Finds features with only one CC1 value
Tester_6
    TEST_CLAUSE = TEST @Value(CC1) CONTAINS ,
    TEST_MODE = Automatic
    TEST_DESCRIPTION = ""
    BOOL_OP = OR
    FAILED -> Matcher_9
Matcher_9
    CNT_ATTR = match_id
    MATCHATTRS = CC1 UFI
    LENIENT_MATCH = No
    BLANK_AND_MISSING_DIFFER = No
    MATCH = 2D
    MATCH_STRATEGY = Match Selected Attributes
    MATCHED -> Matcher_2
Matcher_2
    DIFFATTRS = CC2
    CNT_ATTR = match_id
    MATCHATTRS = UFI
    LENIENT_MATCH = No
    BLANK_AND_MISSING_DIFFER = No
    MATCH = 2D
    MATCH_STRATEGY = Match Selected Attributes
    MATCHED -> Tester_7
    NOT_MATCHED -> Tester_8
Tester_7
    TEST_CLAUSE = TEST @Value(CC2) = ""
    TEST_MODE = Automatic
    TEST_DESCRIPTION = ""
    BOOL_OP = OR
    PASSED -> AttributeCreator_11
    FAILED -> AttributeCreator_13
AttributeCreator_11
    ATTR_LIST = CC2Blank,Yes
    -> Matcher_8
AttributeCreator_13
    ATTR_LIST = CC2Blank,No
    -> Matcher_8
Matcher_8
    DIFFATTRS = CC2Blank
    CNT_ATTR = match_id
    MATCHATTRS = UFI
    LENIENT_MATCH = No
    BLANK_AND_MISSING_DIFFER = No
    MATCH = 2D
    MATCH_STRATEGY = Match Selected Attributes
    MATCHED -> AttributeCreator_14
Tester_8
    TEST_CLAUSE = TEST @Value(DSG) CONTAINS ADM
    TEST_MODE = Automatic
    TEST_DESCRIPTION = ""
    BOOL_OP = OR
    FAILED -> AttributeCreator_14
AttributeCreator_14
    ATTR_LIST = ERROR_RISK,MEDIUM
    -> Multiple_N_Name_Error (writer FILEGDB_1)
Multiple_N_Name_Error (writer FILEGDB_1)
    attributes: RC double, UFI double, UNI double, LAT double, LONG double, DMS_LAT double, DMS_LONG double, MGRS text(150), JOG text(150), FC text(150), DSG text(150), PC text(150), CC1 text(150), ADM1 text(150), POP text(150), ELEV text(150), CC2 text(150), NT text(150), LC text(150), SHORT_FORM text(150), GENERIC text(150), SORT_NAME_RO text(150), FULL_NAME_RO text(150), FULL_NAME_ND_RO text(150), SORT_NAME_RG text(150), FULL_NAME_RG text(150), FULL_NAME_ND_RG text(150), NOTE text(150), MODIFY_DATE text(150), DISPLAY text(150),
      NAME_RANK text(150), NAME_LINK text(150), TRANSL_CD text(150), NM_MODIFY_DATE text(150), match_id text(20), ERROR_RISK text(20)

Bookmark: Duplicate Geometry Errors
  Finds Possible Duplicate Geometry errors. If they also have the same Name and same DSG the error risk is identified as VERY HIGH. If it's any other type of duplicate geomtries with different UFIs the error risk is identified as HIGH unless it is an ADM feature in which case the error risk is low.
Matcher_7
    CNT_ATTR = _match_id
    LENIENT_MATCH = No
    BLANK_AND_MISSING_DIFFER = No
    MATCH = 2D
    MATCH_STRATEGY = Match Selected Attributes
    MATCHED -> Matcher
    NOT_MATCHED -> Matcher_4
Matcher
    CNT_ATTR = match_id
    MATCHATTRS = DSG SORT_NAME_RG
    LENIENT_MATCH = No
    BLANK_AND_MISSING_DIFFER = No
    MATCH = 2D
    MATCH_STRATEGY = Match Selected Attributes
    MATCHED -> AttributeCreator_10
    NOT_MATCHED -> Matcher_3
AttributeCreator_10
    ATTR_LIST = ERROR_RISK,VERY HIGH
    -> Duplicates_Geometries_SameName_SameDSG (writer FILEGDB_1)
Duplicates_Geometries_SameName_SameDSG (writer FILEGDB_1)
    attributes: RC double, UFI double, UNI double, LAT double, LONG double, DMS_LAT double, DMS_LONG double, MGRS text(150), JOG text(150), FC text(150), DSG text(150), PC text(150), CC1 text(150), ADM1 text(150), POP text(150), ELEV text(150), CC2 text(150), NT text(150), LC text(150), SHORT_FORM text(150), GENERIC text(150), SORT_NAME_RO text(150), FULL_NAME_RO text(150), FULL_NAME_ND_RO text(150), SORT_NAME_RG text(150), FULL_NAME_RG text(150), FULL_NAME_ND_RG text(150), NOTE text(150), MODIFY_DATE text(150), DISPLAY text(150),
      NAME_RANK text(150), NAME_LINK text(150), TRANSL_CD text(150), NM_MODIFY_DATE text(150), match_id text(20), ERROR_RISK text(20)
Matcher_3
    DIFFATTRS = UFI
    CNT_ATTR = match_id
    LENIENT_MATCH = No
    BLANK_AND_MISSING_DIFFER = No
    MATCH = 2D
    MATCH_STRATEGY = Match Selected Attributes
    MATCHED -> Tester_5
Tester_5
    TEST_CLAUSE = TEST @Value(DSG) BEGINS_WITH ADM
    TEST_MODE = Automatic
    TEST_DESCRIPTION = ""
    BOOL_OP = OR
    PASSED -> AttributeCreator_9
    FAILED -> AttributeCreator_12
AttributeCreator_9
    ATTR_LIST = ERROR_RISK,LOW
    -> Duplicates_Geometries_Other (writer FILEGDB_1)
AttributeCreator_12
    ATTR_LIST = ERROR_RISK,HIGH
    -> Duplicates_Geometries_Other (writer FILEGDB_1)
Duplicates_Geometries_Other (writer FILEGDB_1)
    attributes: RC double, UFI double, UNI double, LAT double, LONG double, DMS_LAT double, DMS_LONG double, MGRS text(150), JOG text(150), FC text(150), DSG text(150), PC text(150), CC1 text(150), ADM1 text(150), POP text(150), ELEV text(150), CC2 text(150), NT text(150), LC text(150), SHORT_FORM text(150), GENERIC text(150), SORT_NAME_RO text(150), FULL_NAME_RO text(150), FULL_NAME_ND_RO text(150), SORT_NAME_RG text(150), FULL_NAME_RG text(150), FULL_NAME_ND_RG text(150), NOTE text(150), MODIFY_DATE text(150), DISPLAY text(150),
      NAME_RANK text(150), NAME_LINK text(150), TRANSL_CD text(150), NM_MODIFY_DATE text(150), match_id text(20), ERROR_RISK text(20)

Bookmark: Possible Duplicates Errors 3km
  These are Possible Duplicates based on proximity of 3km (but not exact duplicate geometries which other error checks in this model find).
  If the features have the same Name and DSG, the error risk is idenitified as HIGH.
  If the Name is the same and the DSG is different, the error risk is identified as MEDIUM
  If the Name is the same and the DSG is different and if it's a population feature then the error risk is identified as LOW
Matcher_4
    CNT_ATTR = _match_id
    MATCHATTRS = DSG SORT_NAME_RG
    LENIENT_MATCH = No
    BLANK_AND_MISSING_DIFFER = No
    MATCH = NONE
    MATCH_STRATEGY = Match Selected Attributes
    MATCHED -> AttributeCreator_3
    NOT_MATCHED -> Tester_3
AttributeCreator_3
    ATTR_LIST = ERROR_RISK,HIGH
    -> SpatialFilter [input 2]
    -> GeographicBufferer
GeographicBufferer
    BufferUnit = Kilometers
    BufferDist = 3
    CAP_STYLE = Round
    -> AttributeCreator
AttributeCreator
    ATTR_LIST = Length,1
    -> Dissolver
Dissolver
    NO_OVRLP = No
    ACCUM_INPUT_ATTRS = Yes
    GROUP_BY = DSG SORT_NAME_RG
    SUM = Length
    AREA -> Tester
Tester
    TEST_CLAUSE = TEST @Value(Length) = 2
    TEST_MODE = Automatic
    TEST_DESCRIPTION = ""
    BOOL_OP = OR
    PASSED -> SpatialFilter [input 1]
    PASSED -> Possible_Duplicate_Location_3Km (writer FILEGDB_1)
SpatialFilter
    PREDATTR = _predicate
    MERGE_ATTRS = Yes
    BASE_TYPE = Multiple Filters
    PREDICATE_VALUE = Intersects
    USE_BOUNDING_BOX = No
    PASS_CRITERIA = Pass Against One Filter
    GROUP_BY = SORT_NAME_RG
    CURVE_BOUNDARY_RULE_PARAM = Default Rule
    PASSED -> Possible_Duplicate_3Km (writer FILEGDB_1)
    FAILED -> Tester_9
Tester_3
    TEST_CLAUSE = TEST @Value(DSG) BEGINS_WITH PP
    TEST_MODE = Automatic
    TEST_DESCRIPTION = ""
    BOOL_OP = OR
    FAILED -> Matcher_5
    PASSED -> AttributeCreator_8
Matcher_5
    DIFFATTRS = DSG
    CNT_ATTR = _match_id
    MATCHATTRS = SORT_NAME_RG
    LENIENT_MATCH = No
    BLANK_AND_MISSING_DIFFER = No
    MATCH = NONE
    MATCH_STRATEGY = Match Selected Attributes
    MATCHED -> AttributeCreator_7
AttributeCreator_7
    ATTR_LIST = ERROR_RISK,MEDIUM
    -> GeographicBufferer_2
    -> SpatialFilter_2 [input 2]
GeographicBufferer_2
    BufferUnit = Kilometers
    BufferDist = 3
    CAP_STYLE = Round
    -> AttributeCreator_5
AttributeCreator_5
    ATTR_LIST = Length,1
    -> Dissolver_2
Dissolver_2
    NO_OVRLP = No
    ACCUM_INPUT_ATTRS = Yes
    GROUP_BY = SORT_NAME_RG
    SUM = Length
    AREA -> Tester_2
Tester_2
    TEST_CLAUSE = TEST @Value(Length) = 2
    TEST_MODE = Automatic
    TEST_DESCRIPTION = ""
    BOOL_OP = OR
    PASSED -> SpatialFilter_2 [input 1]
    PASSED -> Possible_Duplicate_Location_3Km (writer FILEGDB_1)
SpatialFilter_2
    PREDATTR = _predicate
    MERGE_ATTRS = Yes
    BASE_TYPE = Multiple Filters
    PREDICATE_VALUE = Intersects
    USE_BOUNDING_BOX = No
    PASS_CRITERIA = Pass Against One Filter
    GROUP_BY = SORT_NAME_RG
    CURVE_BOUNDARY_RULE_PARAM = Default Rule
    FAILED -> Tester_9
    PASSED -> Possible_Duplicate_3Km (writer FILEGDB_1)
AttributeCreator_8
    ATTR_LIST = ERROR_RISK,LOW
    -> Matcher_6
Matcher_6
    DIFFATTRS = DSG
    CNT_ATTR = _match_id
    MATCHATTRS = SORT_NAME_RG
    LENIENT_MATCH = No
    BLANK_AND_MISSING_DIFFER = No
    MATCH = NONE
    MATCH_STRATEGY = Match Selected Attributes
    MATCHED -> AttributeCreator_6
AttributeCreator_6
    ATTR_LIST = ERROR_RISK,LOW
    -> GeographicBufferer_3
    -> SpatialFilter_3 [input 2]
GeographicBufferer_3
    BufferUnit = Kilometers
    BufferDist = 3
    CAP_STYLE = Round
    -> AttributeCreator_4
AttributeCreator_4
    ATTR_LIST = Length,1
    -> Dissolver_3
Dissolver_3
    NO_OVRLP = No
    ACCUM_INPUT_ATTRS = Yes
    GROUP_BY = SORT_NAME_RG
    SUM = Length
    AREA -> Tester_4
Tester_4
    TEST_CLAUSE = TEST @Value(Length) = 2
    TEST_MODE = Automatic
    TEST_DESCRIPTION = ""
    BOOL_OP = OR
    PASSED -> SpatialFilter_3 [input 1]
    PASSED -> Possible_Duplicate_Location_3Km (writer FILEGDB_1)
Possible_Duplicate_Location_3Km (writer FILEGDB_1)
    attributes: RC double, UFI double, UNI double, LAT double, LONG double, DMS_LAT double, DMS_LONG double, MGRS text(150), JOG text(150), FC text(150), DSG text(150), PC text(150), CC1 text(150), ADM1 text(150), POP text(150), ELEV text(150), CC2 text(150), NT text(150), LC text(150), SHORT_FORM text(150), GENERIC text(150), SORT_NAME_RO text(150), FULL_NAME_RO text(150), FULL_NAME_ND_RO text(150), SORT_NAME_RG text(150), FULL_NAME_RG text(150), FULL_NAME_ND_RG text(150), NOTE text(150), MODIFY_DATE text(150), DISPLAY text(150),
      NAME_RANK text(150), NAME_LINK text(150), TRANSL_CD text(150), NM_MODIFY_DATE text(150), ERROR_RISK text(150)
SpatialFilter_3
    PREDATTR = _predicate
    MERGE_ATTRS = Yes
    BASE_TYPE = Multiple Filters
    PREDICATE_VALUE = Intersects
    USE_BOUNDING_BOX = No
    PASS_CRITERIA = Pass Against One Filter
    GROUP_BY = SORT_NAME_RG
    CURVE_BOUNDARY_RULE_PARAM = Default Rule
    FAILED -> Tester_9
    PASSED -> Possible_Duplicate_3Km (writer FILEGDB_1)
Possible_Duplicate_3Km (writer FILEGDB_1)
    attributes: RC double, UFI double, UNI double, LAT double, LONG double, DMS_LAT double, DMS_LONG double, MGRS text(150), JOG text(150), FC text(150), DSG text(150), PC text(150), CC1 text(150), ADM1 text(150), POP text(150), ELEV text(150), CC2 text(150), NT text(150), LC text(150), SHORT_FORM text(150), GENERIC text(150), SORT_NAME_RO text(150), FULL_NAME_RO text(150), FULL_NAME_ND_RO text(150), SORT_NAME_RG text(150), FULL_NAME_RG text(150), FULL_NAME_ND_RG text(150), NOTE text(150), MODIFY_DATE text(150), DISPLAY text(150),
      NAME_RANK text(150), NAME_LINK text(150), TRANSL_CD text(150), NM_MODIFY_DATE text(150), ERROR_RISK text(20)

Bookmark: Possible Duplicate Errors 50Km
  These are Possible Duplicates based on proximity of 50km (but not exact duplicate geometries or within 3km which other error checks in this model find).
  These are separated into Hypso and Hydro features.
  If it is a Hypso Feature with the same name it is identified as a LOW error risk.
  If it is a Hydro (STM or STMI) Feature with the same name it is identified as a LOW error risk.
Tester_9
    TEST_CLAUSE:
      TEST @Value(DSG) = MT
      TEST @Value(DSG) = HLL
      TEST @Value(DSG) = RDGE
      TEST @Value(DSG) = PK
      TEST @Value(DSG) = MTS
    TEST_MODE = Automatic
    TEST_DESCRIPTION = ""
    BOOL_OP = OR
    FAILED -> Tester_10
    PASSED -> AttributeCreator_17
AttributeCreator_17
    ATTR_LIST = DSG_Gen,Hypso
    -> Matcher_10
Matcher_10
    CNT_ATTR = match_id
    MATCHATTRS = DSG_Gen SORT_NAME_RG
    LENIENT_MATCH = No
    BLANK_AND_MISSING_DIFFER = No
    MATCH = NONE
    MATCH_STRATEGY = Match Selected Attributes
    MATCHED -> GeographicBufferer_5
    MATCHED -> SpatialFilter_5 [input 2]
GeographicBufferer_5
    BufferUnit = Kilometers
    BufferDist = 50
    CAP_STYLE = Round
    -> AttributeCreator_16
AttributeCreator_16
    ATTR_LIST = Length,1
    -> Dissolver_5
Dissolver_5
    NO_OVRLP = No
    ACCUM_INPUT_ATTRS = Yes
    GROUP_BY = SORT_NAME_RG _match_id
    SUM = Length
    AREA -> Tester_12
Tester_12
    TEST_CLAUSE = TEST @Value(Length) = 2
    TEST_MODE = Automatic
    TEST_DESCRIPTION = ""
    BOOL_OP = OR
    PASSED -> SpatialFilter_5 [input 1]
SpatialFilter_5
    PREDATTR = _predicate
    MERGE_ATTRS = Yes
    BASE_TYPE = Multiple Filters
    PREDICATE_VALUE = Intersects
    USE_BOUNDING_BOX = No
    PASS_CRITERIA = Pass Against One Filter
    GROUP_BY = SORT_NAME_RG
    CURVE_BOUNDARY_RULE_PARAM = Default Rule
    PASSED -> AttributeCreator_19
AttributeCreator_19
    ATTR_LIST = ERROR_RISK,LOW
    -> Possible_Duplicate_100Km_Hypso (writer FILEGDB_1)
Possible_Duplicate_100Km_Hypso (writer FILEGDB_1)
    attributes: RC double, UFI double, UNI double, LAT double, LONG double, DMS_LAT double, DMS_LONG double, MGRS text(150), JOG text(150), FC text(150), DSG text(150), PC text(150), CC1 text(150), ADM1 text(150), POP text(150), ELEV text(150), CC2 text(150), NT text(150), LC text(150), SHORT_FORM text(150), GENERIC text(150), SORT_NAME_RO text(150), FULL_NAME_RO text(150), FULL_NAME_ND_RO text(150), SORT_NAME_RG text(150), FULL_NAME_RG text(150), FULL_NAME_ND_RG text(150), NOTE text(150), MODIFY_DATE text(150), DISPLAY text(150),
      NAME_RANK text(150), NAME_LINK text(150), TRANSL_CD text(150), NM_MODIFY_DATE text(150), ERROR_RISK text(150), match_id text(150)
Tester_10
    TEST_CLAUSE:
      TEST @Value(DSG) = STM
      TEST @Value(DSG) = STMI
    TEST_MODE = Automatic
    TEST_DESCRIPTION = ""
    BOOL_OP = OR
    PASSED -> AttributeCreator_18
AttributeCreator_18
    ATTR_LIST = DSG_Gen,Hydro
    -> Matcher_11
Matcher_11
    CNT_ATTR = match_id
    MATCHATTRS = DSG_Gen SORT_NAME_RG
    LENIENT_MATCH = No
    BLANK_AND_MISSING_DIFFER = No
    MATCH = NONE
    MATCH_STRATEGY = Match Selected Attributes
    MATCHED -> GeographicBufferer_4
    MATCHED -> SpatialFilter_4 [input 2]
GeographicBufferer_4
    BufferUnit = Kilometers
    BufferDist = 50
    CAP_STYLE = Round
    -> AttributeCreator_15
AttributeCreator_15
    ATTR_LIST = Length,1
    -> Dissolver_4
Dissolver_4
    NO_OVRLP = No
    ACCUM_INPUT_ATTRS = Yes
    GROUP_BY = SORT_NAME_RG
    SUM = Length
    AREA -> Tester_11
Tester_11
    TEST_CLAUSE = TEST @Value(Length) = 2
    TEST_MODE = Automatic
    TEST_DESCRIPTION = ""
    BOOL_OP = OR
    PASSED -> SpatialFilter_4 [input 1]
SpatialFilter_4
    PREDATTR = _predicate
    MERGE_ATTRS = Yes
    BASE_TYPE = Multiple Filters
    PREDICATE_VALUE = Intersects
    USE_BOUNDING_BOX = No
    PASS_CRITERIA = Pass Against One Filter
    GROUP_BY = SORT_NAME_RG
    CURVE_BOUNDARY_RULE_PARAM = Default Rule
    PASSED -> AttributeCreator_20
AttributeCreator_20
    ATTR_LIST = ERROR_RISK,LOW
    -> Possible_Duplicate_100Km_Hydro (writer FILEGDB_1)
Possible_Duplicate_100Km_Hydro (writer FILEGDB_1)
    attributes: RC double, UFI double, UNI double, LAT double, LONG double, DMS_LAT double, DMS_LONG double, MGRS text(150), JOG text(150), FC text(150), DSG text(150), PC text(150), CC1 text(150), ADM1 text(150), POP text(150), ELEV text(150), CC2 text(150), NT text(150), LC text(150), SHORT_FORM text(150), GENERIC text(150), SORT_NAME_RO text(150), FULL_NAME_RO text(150), FULL_NAME_ND_RO text(150), SORT_NAME_RG text(150), FULL_NAME_RG text(150), FULL_NAME_ND_RG text(150), NOTE text(150), MODIFY_DATE text(150), DISPLAY text(150),
      NAME_RANK text(150), NAME_LINK text(150), TRANSL_CD text(150), NM_MODIFY_DATE text(150), ERROR_RISK text(150), match_id text(150)
