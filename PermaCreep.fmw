FME workspace PermaCreep.fmw

Parameters:
- Output_CSV = C:\GCT\R&D\Perma_Creep   # Output Folder for CSV File

Readers:
- XLSXR_1: XLSXR from C:/GCT/Creeper_LanguageStats_Dwellings/Emoticons.xlsx
- XLSXR_2: XLSXR from C:/GCT/R&D/Language_Evaluator/Leets.xlsx

Writers:
- CSV_1: CSV to $(Output_CSV)

Bookmark: Tweet_Streamer
  Streams live tweets from twitter and only keeps Geotagged tweets. Once a Geotagged tweet is discovered the model pulls from that users profile to get the last up to 200 geotagged tweets that user made. All tweet information is kept. Useful tweet information are stored as values in a field.
Creator
    GEOMTYPE = Geometry Object
    NUM = 1
    CREATED -> TweetStreamer
Note: Streaming live tweets
TweetStreamer
    POINT_BUFFER = 0
    TWITTER_USERNAME = tivelp@gmail.com
    USE_GEOMETRY = Yes
    TWITTER_PASSWORD =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
    TWEETS -> Decelerator
Note: Pulling Coordinates of Tweets and testing to see if there are valid coordinates. Those that do not are thrown away
Decelerator
    DECEL_TYPE = Limit Features Per Second
    FEATURES_PER_SECOND = 50
    -> StringSearcher_4
StringSearcher_4
    REGEXP = coordinates":.*?.,
    MATCHED_RESULT_ATTR = coords
    STRING_TO_SEARCH = @Value(_tweet_search_result)
    MATCHED_PARTS_ATTR = _matched_parts
    CASE = no
    MATCHED -> SubstringExtractor_2
SubstringExtractor_2
    RESULT_ATTR = CoordTest
    SRC_ATTR = coords
    END = -1
    START = 14
    -> Tester_3
Tester_3
    BOOL_OP = OR
    TEST_DESCRIPTION = ""
    TEST_MODE = Automatic
    TEST_CLAUSE = TEST @Value(CoordTest) = ull,
    PASSED -> Tester_2_Passed
    FAILED -> TwitterStatusFetcher
Tester_2_Passed: Inspector
Note: Retrieving up to 200 geotagged tweets from / discovered user with geotagged tweets
TwitterStatusFetcher
    TWITTER_REQUEST_TYPE = User
    TWITTER_USERNAME = tivelp@gmail.com
    TWITTER_TIMELINE = @Value(_tweet_username)
    TWITTER_PASSWORD =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
    TWITTER_STATUS_COUNT = 200
    TWEETS -> CoordinateExtractor
CoordinateExtractor
    X_ATTR = x
    Z_ATTR = z
    IND = 0
    Z_DEFAULT = -9999
    Y_ATTR = y
    -> StringSearcher_3
StringSearcher_3
    REGEXP = time_zone.*?.,
    MATCHED_RESULT_ATTR = tzone
    STRING_TO_SEARCH = @Value(_tweet_search_result)
    MATCHED_PARTS_ATTR = _matched_parts
    CASE = no
    MATCHED -> StringSearcher_5
StringSearcher_5
    REGEXP = location.*?.,
    MATCHED_RESULT_ATTR = location
    STRING_TO_SEARCH = @Value(_tweet_search_result)
    MATCHED_PARTS_ATTR = _matched_parts
    CASE = no
    MATCHED -> StringSearcher_6
StringSearcher_6
    REGEXP = lang.*?.,
    MATCHED_RESULT_ATTR = language
    STRING_TO_SEARCH = @Value(_tweet_search_result)
    MATCHED_PARTS_ATTR = _matched_parts
    CASE = no
    MATCHED -> SubstringExtractor
SubstringExtractor
    RESULT_ATTR = Timezone
    SRC_ATTR = tzone
    END = -3
    START = 12
    -> SubstringExtractor_3
SubstringExtractor_3
    RESULT_ATTR = Location
    SRC_ATTR = location
    END = -3
    START = 11
    -> SubstringExtractor_4
SubstringExtractor_4
    RESULT_ATTR = Language
    SRC_ATTR = language
    END = -3
    START = 7
    -> DuplicateRemover_2
Note: Removing Duplicate Tweets
DuplicateRemover_2
    KEYATTR = _tweet_status
    UNIQUE -> AttributeRenamer
AttributeRenamer
    ATTR_LIST = _tweet_created_at,Date,,_tweet_id,Twitter_ID,,_tweet_username,Twitter_User,,_tweet_status,Twitter_Text,,_tweet_search_result,Metadata,,y,Lat,,x,Long,
    -> AttributeCreator

Bookmark: Language Statistics Tool
  Derivies Language statistics and performs emoticon and leet detection on input content. Outputs additional information as values in fields in a csv file. Preserves orginal information as well
Note: Creating an attribute called "List Counter" / to be used in a later transformer to index a list.
AttributeCreator
    ATTR_LIST = list_counter,0,Content,@Value(Twitter_Text)
    -> StringLengthCalculator
Note: Calculating the length of the content field. / Needed for the Content Looper
StringLengthCalculator
    LENGTH_ATTR = _length
    SRC_ATTR = Content
    -> AttributeCreator_2
Note: Creating a counter to be used to track / iterations in the Content Looper loop.
AttributeCreator_2
    ATTR_LIST = ContentCounter,0
    -> AttributeCreator_3
Note: Creating the new attribute that will hold the characters in the content field / separated by a space. they need to be separated by a space so a list can be / made out of the characters and run in the Lister Loop.
AttributeCreator_3
    ATTR_LIST = Content_Spacer,""
    -> AttributeCreator_5
Note: Creating CodeAll variable so it can be used in Content Loop
AttributeCreator_5
    ATTR_LIST = CodeAll,""
    -> AttributeCreator_4
Note: Creating Languageall variable to be used in Content Loop
AttributeCreator_4
    ATTR_LIST = LanguageAll,""
    -> Content_Looper
Note: Custom transformer to loop through and accumulate the languages of each character
Content_Looper: Content Loop
    -> AttributeSplitter
Note: Add all Languages from the LanguageAll field to a list
AttributeSplitter
    ATTR_NAME = LanguageAll
    DROP_EMPTY_PARTS = Yes
    DELIMITER = " "
    TRIM_OPTION = Both
    LIST_NAME = LanguageList
    -> AttributeSplitter_2
Note: Add all codes from the CodeAll field to a list
AttributeSplitter_2
    ATTR_NAME = CodeAll
    DROP_EMPTY_PARTS = Yes
    DELIMITER = " "
    TRIM_OPTION = Both
    LIST_NAME = CodeList
    -> ListHistogrammer_2
Note: Creates a list of statistical attributes associated / with the languages used for row of data. This includes / a list of languages used that does not repeat the language / multiple times. It also includes a list of the frequency a / given language is used.
ListHistogrammer_2
    SRC_LIST = CodeList{}
    LIST_NAME = _histogramcode
    -> ListHistogrammer
Note: Creates a list of statistical attributes associated / with the languages used for row of data. This includes / a list of languages used that does not repeat the language / multiple times. It also includes a list of the frequency a / given language is used.
ListHistogrammer
    SRC_LIST = LanguageList{}
    LIST_NAME = _histogram
    -> ListConcatenator_4
Note: Concatenates the list of languages that are unique values / created from the ListHistogrammer. This is shown in the final / output under the "Languages" field
ListConcatenator_4
    LIST_ATTR = _histogram{}.value
    SEP = "; "
    DROP_EMPTY_PARTS = No
    VAL_ATTR = Languages
    -> ListConcatenator_2
Note: Concatenates the list of languages that are unique values / created from the ListHistogrammer. This is shown in the final / output under the "Languages" field
ListConcatenator_2
    LIST_ATTR = _histogramcode{}.value
    SEP = "; "
    DROP_EMPTY_PARTS = No
    VAL_ATTR = CharacterCodes
    -> ListConcatenator_5
Note: Concatenates the lists showing the frequency of / languages being used for a single row of data. / The results can be seen in the Language_Frequency / field of the final data.
ListConcatenator_5
    LIST_ATTR = _histogram{}.count
    SEP = "; "
    DROP_EMPTY_PARTS = No
    VAL_ATTR = Language_Frequency
    -> PythonCaller
Note: Python code that returns language grouping / statistics and detects possible emoticons
PythonCaller
    PYTHONSOURCE:
      #This script is does and returns several things. It finds if something is multi lingual or a sinlge language, as well if it is a possibe emoticon that isnt in emoticon excel file.
      #In addtion it performs a varaeity of statistics on the content of the data. If the Languages are "AAAAAAABBBBCDEEEEEEAAAAA" the script formats it as 7A 4B 1C 1D 6E 5A. This helps
      #determine if it is multi lingual and gives another usefull statistic of the data.
      import fmeobjects, re
      def LanguageGroup(feature):

          #Def function that will checks if all things in the list are the same language
          def all_same(items):
              return all(x == items[0] for x in items)
          #Represents the LanguageAll field that contains the language of each character code
          languageString = feature.getAttribute("LanguageAll")
          contentString = feature.getAttribute("Content")
          contentList = list(contentString)
          #Creating a list from the LanguageAll field string using a space as the delimiter
          languageList = languageString.split(" ")

          #Setting up counters and empty variables to be used shortly
          groupCounter = 1
          loopCounter = 0
          pattern = ""
          patternList =[]
          patternList2 =[]


          for group in languageList:

              try:
                  #Checking if the next item in the list is the same item as the current item, if so then
                  #the count of that language type is increased.
                  if languageList[loopCounter+1] == group:
                      groupCounter += 1
                      loopCounter += 1
                  #If the next item in the Language list is not the same as the current item then a new language
                  #group with a reset counter is started
                  else:
                      groupcount = str(groupCounter) + "(" + group + ")"
                      pattern = pattern + " " + groupcount
                      patternList.append(groupCounter)
                      patternList2.append(group)
                      groupCounter = 1
                      loopCounter += 1

              #This except occurs when the try statement above runs into the end of the list and can't check
              #what's after the last item in the list.
              except:
                  groupcount = str(groupCounter) + "(" + group + ")"
                  pattern = pattern + " " + groupcount
                  #patfin represents the language and the group count eg. [5(Arabic), 3(Basic_Latin), 8(Arabic)]
                  patfin = pattern[5:-3]
                  patternList.append(groupCounter)
                  patternList2.append(group)

          #patlistgc represents just the number in patfin eg. [5,3,8] This will be what allows us to find
          #single vs multiple languages in the content and later possible emoticons
          patlistgc = patternList[1:-1]
          #patlistg represents just the language in patfin eg. [Arabic,Basic_Latin, Arabic]
          patlistg = patternList2[1:-1]
          #Changing palistgc to string to aid in the search of emoticons [5,3,8] will now appear as 5_3_8
          #we are doing this to find the pattern 1_1_1 which will identify a possible emoticon

          indexpos = 0
          possemotechar=''
          ltype = ''
          possemote = ''


          for group in patlistgc:
              try:
                  #Variable containing conditions for if statement to find possible emoticons. Ignoring Ignore Characters. Farsi, and Latin supplements and extended
                  #because they cause to many false positives to get through.
                  condition1 = patlistgc[indexpos] == 1 and patlistgc[indexpos+1] == 1 and patlistgc[indexpos+2] == 1
                  condition2 = patlistg[indexpos] != "Ignore_Character" and patlistg[indexpos+1] != "Ignore_Character"and patlistg[indexpos+2] != "Ignore_Character"
                  condition3 = patlistg[indexpos] != "Latin-1_Supplement" and patlistg[indexpos+1] != "Latin-1_Supplement"and patlistg[indexpos+2] != "Latin-1_Supplement"
                  condition4 = patlistg[indexpos] != "Latin_Extended-A" and patlistg[indexpos+1] != "Latin_Extended-A"and patlistg[indexpos+2] != "Latin_Extended-A"
                  condition5 = patlistg[indexpos] != "Latin_Extended-B" and patlistg[indexpos+1] != "Latin_Extended-B"and patlistg[indexpos+2] != "Latin_Extended-B"
                  condition6 = patlistg[indexpos] != "Farsi" and patlistg[indexpos+1] != "Farsi"and patlistg[indexpos+2] != "Farsi"
                  if condition1 and condition2 and condition3 and condition4 and condition5 and condition6:

                      contentpos = 0
                      for x in patlistgc[0:indexpos]:
                          contentpos = contentpos + x
                      indexpos+=1
                      possemotechar = possemotechar + contentList[contentpos] + contentList[contentpos+1] + contentList[contentpos+2] + '    '
                      possemote = "Possible Emoticon"

                  else:
                      indexpos += 1
              except:
                  break

          #We don't want special characters like a space, period, octothorp, etc to count towards something being
          #multiple languages or a possilbe emoticon. The below code causes these characters to be ignored in this
          #type of consideration. We are sssuming emoticons that use these symbols are caught in the
          #input emoticon file in the FME model.
          indexpos = 0

          for group in patlistg:
              if group == "Ignore_Character":

                  patlistg.remove(group)
                  del(patlistgc[indexpos])
                  indexpos += 1

              else:
                  indexpos += 1

          contentpos = 0
          for item in languageList:

              try:
                  if item == "Ignore_Character":
                      del(contentList[contentpos])

                  else:
                      contentpos+=1
              except:
                  break


          #Checking to see if content is single or multi language using def function all_same() created at the start
          for group in patlistg:

              if all_same(patlistg) == True:
                  ltype = "Single Language"
              else:
                  ltype = "Multi Language"



          feature.setAttribute("LanguageGrouping", patfin)
          feature.setAttribute("LanguageType", ltype)
          feature.setAttribute("PossibleEmoteChar", possemotechar)
          feature.setAttribute("EmoticonDetection", possemote)
    PYTHONSYMBOL = LanguageGroup
    NEW_ATTRIBUTES = LanguageGrouping LanguageType PossibleEmoteChar EmoticonDetection
    -> Tester
Note: If items in tester are found in the possible emoticon detection field then they are removed / as they are not possible emoticons
Tester
    BOOL_OP = OR
    TEST_DESCRIPTION = ""
    TEST_MODE = Automatic
    TEST_CLAUSE:
      TEST @Value(PossibleEmoteChar) = I'm
      TEST @Value(PossibleEmoteChar) = I'd
    PASSED -> AttributeCreator_8
    FAILED -> AttributeFilter
AttributeCreator_8
    ATTR_LIST = PossibleEmoteChar,"",EmoticonDetection,""
    -> AttributeFilter
AttributeFilter
    ATTR_NAME = LanguageType
    ATTR_VALUES = <EMPTY>,Multi Language,Single Language,<MISSING>,<NULL>,<UNFILTERED>
    Multi Language -> GeotaggedTweets_LanguageStats3 (writer CSV_1)
    Single Language -> GeotaggedTweets_LanguageStats3 (writer CSV_1)
    <MISSING> -> GeotaggedTweets_LanguageStats3 (writer CSV_1)
    <NULL> -> GeotaggedTweets_LanguageStats3 (writer CSV_1)
    <UNFILTERED> -> GeotaggedTweets_LanguageStats3 (writer CSV_1)
    <EMPTY> -> GeotaggedTweets_LanguageStats3 (writer CSV_1)
Note: Final Geotagged tweet info with additional language statistic information
GeotaggedTweets_LanguageStats3 (writer CSV_1)
    attributes: Twitter_ID text, Twitter_Text text, Date text, Metadata text, Twitter_User text, Location text, Language text, Timezone text, Lat text, Long text, LanguageGrouping text, LanguageType text, Languages text, Language_Frequency text

FME custom transformer Lister Loop

Note: Entry point for data into the List Looper
INPUT (input)
    -> ListElementCounter
Note: Counts the number of elements in each list / created from the "Content" field.
ListElementCounter
    CNT_ATTR = _element_count
    LIST_NAME = _list{}
    -> ListIndexer
Note: Uses the List Counter created at the start of the model / to index each position in the list. List Counter starts at 0 / and increments one each time through the loop.
ListIndexer
    LIST_ATTR = _list{}
    INDEX = @Value(list_counter)
    -> CharacterCodeExtractor
Note: Extracts the numerical character code of the first letter / of each element in the "Content" list.
CharacterCodeExtractor
    CODE_ATTR = _code
    SRC_ATTR = _list
    -> AttributeRangeMapper
Note: Creates many different ranges of numbers that corelate / to a different character code.
AttributeRangeMapper
    OUT_ATTR = Language
    IN_ATTR = _code
    LUT = 0,127,Basic_Latin,1536,1791,Arabic,128,255,Latin-1 Supplement,256,383,Latin Extended-A,384,591,Latin Extended-B,19968,40959,Chinese_Japanese_Korean_Unified_Ideographs,1024,1279,Cyrillic,592,687,IPA Extensions,688,767,Spacing Modifier Letters,768,879,Combining Diacritical Marks,880,1023,Greek,1328,1423,Armenian,1424,1535,Hebrew,1792,1871,Syriac,1920,1983,Thaana,2304,2431,Devanagari,2432,2559,Bengali,2560,2687,Gurmukhi,2688,2815,Gujarati,2816,2943,Oriya,2944,3071,Tamil,3072,3199,Telugu,3200,3327,Kannada,3328,3455,Malayalam,3456,3583,Sinhala,3584,3711,Thai,3712,3839,Lao,3840,4095,Tibetan,4096,4255,Myanmar,4256,4351,Georgian,4352,4607,Hangul Jamo,4608,4991,Ethiopic,5024,5119,Cherokee,5120,5759,Unified Canadian Aboriginal Syllabics,5760,5791,Ogham,5792,5887,Runic,6016,6143,Khmer,6144,6319,Mongolian,7680,7935,Latin Extended Additional,7936,8191,Greek Extended,8192,8303,General Punctuation,8304,8351,Superscripts and Subscripts,8352,8399,Currency Symbols,8400,8447,Combining Marks for Symbols,8448,8527,Letterlike Symbols,8528,8591,Number Forms,8592,8703,Arrows,8704,8959,Mathematical Operators,8960,9215,Miscellaneous Technical,9216,9279,Control Pictures,9280,9311,Optical Character Recognition,9312,9471,Enclosed Alphanumerics,9472,9599,Box Drawing,9600,9631,Block Elements,9632,9727,Geometric Shapes,9728,9983,Miscellaneous Symbols,9984,10175,Dingbats,10240,10495,Braille Patterns,11904,12031,CJK Radicals Supplement,12032,12255,Kangxi Radicals,12272,12287,Ideographic Description Characters,12288,12351,CJK Symbols and Punctuation,12352,12447,Hiragana,12448,12543,Katakana,12544,12591,Bopomofo,12592,12687,Hangul Compatibility Jamo,12688,12703,Kanbun,12704,12735,Bopomofo Extended,12800,13055,Enclosed CJK Letters and Months,13056,13311,CJK Compatibility,13312,19893,CJK Unified Ideographs Extension A,40960,42127,Yi Syllables,42128,42191,Yi Radicals,44032,55203,Hangul Syllables,55296,56191,High Surrogates,56192,56319,High Private Use Surrogates,56320,57343,Low Surrogates,57344,63743,Private Use,63744,64255,CJK Compatibility Ideographs,64256,64335,Alphabetic Presentation Forms,64336,65023,Arabic Presentation Forms-A,65056,65071,Combining Half Marks,65072,65103,CJK Compatibility Forms,65104,65135,Small Form Variants,65136,65278,Arabic Presentation Forms-B,65279,65279,Specials,65280,65519,Halfwidth and Fullwidth Forms,65520,65533,Specials,1740,1740,Farsi,9771,9771,Farsi,64508,64511,Farsi,1662,1662,Farsi,1670,1670,Farsi,1688,1688,Farsi,1711,1711,Farsi,,,
    -> AttributeCreator
Note: Increments the list counter by 1 / so that the next time through the / loop the next element in the / "Content" list is indexed.
AttributeCreator
    ATTR_LIST = list_counter,@Evaluate(@Value(list_counter)+1)
    -> Tester
Note: If the incremented list counter equals the total / number of elements in the list, then the loop ends / and output is sent out of the list looper. If it is less / than the elements in the list then it does another loop.
Tester
    BOOL_OP = OR
    TEST_DESCRIPTION = ""
    TEST_MODE = Automatic
    TEST_CLAUSE = TEST @Value(list_counter) = @Value(_element_count)
    FAILED -> INPUT (output)
    PASSED -> OUTPUT (output)
    FAILED -> OUTPUT (output)
Note: Output out of the Lister Loop if the tester / conditions are met
OUTPUT (output)
Note: Loops back to the Lister Loop input if the tester / conditions are not met.
INPUT (output)

FME custom transformer Content Loop

INPUT (input)
    -> SubstringExtractor
Note: Looking at one character in the content field / each time through the loop
SubstringExtractor
    RESULT_ATTR = _substring
    SRC_ATTR = Content
    END = @Value(ContentCounter)
    START = @Value(ContentCounter)
    -> CharacterCodeExtractor
Note: Creates many different ranges of numbers that corelate / to a different character code.
CharacterCodeExtractor
    CODE_ATTR = _code
    SRC_ATTR = _substring
    -> AttributeFilter
Note: Filters out Farsi characters. Wil be replaced with a tester at a later time
AttributeFilter
    ATTR_NAME = _code
    ATTR_VALUES = <BLANK>,<UNFILTERED>,1740,9771,64511,1662,1670,1688,1711
    1740 -> AttributeCreator_5
    9771 -> AttributeCreator_5
    64511 -> AttributeCreator_5
    1670 -> AttributeCreator_5
    1662 -> AttributeCreator_5
    1688 -> AttributeCreator_5
    1711 -> AttributeCreator_5
    <BLANK> -> AttributeRangeMapper
    <UNFILTERED> -> AttributeRangeMapper
Note: Creates many different ranges of numbers that corelate / to a different character code.
AttributeRangeMapper
    OUT_ATTR = Language
    IN_ATTR = _code
    LUT = 1536,1791,Arabic,128,255,Latin-1_Supplement,256,383,Latin_Extended-A,384,591,Latin_Extended-B,19968,40959,Chinese_Japanese_Korean_Unified_Ideographs,1024,1279,Cyrillic,592,687,IPA_Extensions,688,767,Spacing_Modifier_Letters,768,879,Combining_Diacritical_Marks,880,1023,Greek,1328,1423,Armenian,1424,1535,Hebrew,1792,1871,Syriac,1920,1983,Thaana,2304,2431,Devanagari,2432,2559,Bengali,2560,2687,Gurmukhi,2688,2815,Gujarati,2816,2943,Oriya,2944,3071,Tamil,3072,3199,Telugu,3200,3327,Kannada,3328,3455,Malayalam,3456,3583,Sinhala,3584,3711,Thai,3712,3839,Lao,3840,4095,Tibetan,4096,4255,Myanmar,4256,4351,Georgian,4352,4607,Hangul_Jamo,4608,4991,Ethiopic,5024,5119,Cherokee,5120,5759,Unified_Canadian_Aboriginal_Syllabics,5760,5791,Ogham,5792,5887,Runic,6016,6143,Khmer,6144,6319,Mongolian,7680,7935,Latin_Extended_Additional,7936,8191,Greek_Extended,8192,8303,General_Punctuation,8304,8351,Superscripts_and_Subscripts,8352,8399,Currency_Symbols,8400,8447,Combining_Marks_for_Symbols,8448,8527,Letterlike_Symbols,8528,8591,Number_Forms,8592,8703,Arrows,8704,8959,Mathematical_Operators,8960,9215,Miscellaneous_Technical,9216,9279,Control_Pictures,9280,9311,Optical_Character_Recognition,9312,9471,Enclosed_Alphanumerics,9472,9599,Box_Drawing,9600,9631,Block_Elements,9632,9727,Geometric_Shapes,9728,9983,Miscellaneous_Symbols,9984,10175,Dingbats,10240,10495,Braille_Patterns,11904,12031,CJK_Radicals_Supplement,12032,12255,Kangxi_Radicals,12272,12287,Ideographic_Description_Characters,12288,12351,CJK_Symbols_and_Punctuation,12352,12447,Hiragana,12448,12543,Katakana,12544,12591,Bopomofo,12592,12687,Hangul_Compatibility_Jamo,12688,12703,Kanbun,12704,12735,Bopomofo_Extended,12800,13055,Enclosed_CJK_Letters_and_Months,13056,13311,CJK_Compatibility,13312,19893,CJK_Unified_Ideographs_Extension_A,40960,42127,Yi_Syllables,42128,42191,Yi_Radicals,44032,55203,Hangul_Syllables,55296,56191,High_Surrogates,56192,56319,High_Private_Use_Surrogates,56320,57343,Low_Surrogates,57344,63743,Private_Use,63744,64255,CJK_Compatibility_Ideographs,64256,64335,Alphabetic_Presentation_Forms,64336,65023,Arabic_Presentation_Forms-A,65056,65071,Combining_Half_Marks,65072,65103,CJK_Compatibility_Forms,65104,65135,Small_Form_Variants,65136,65278,Arabic_Presentation_Forms-B,65279,65279,Specials,65280,65519,Halfwidth_and_Fullwidth_Forms,65520,65533,Specials,32,47,Ignore_Character,58,64,Ignore_Character,91,96,Ignore_Character,123,127,Ignore_Character,0,31,Basic_Latin,48,57,Basic_Latin,65,90,Basic_Latin,97,122,Basic_Latin,,,
    -> Tester_2
Note: Checks for speical characters like punctuation so they are not identified as a language
Tester_2
    BOOL_OP = OR
    TEST_DESCRIPTION = ""
    TEST_MODE = Automatic
    TEST_CLAUSE = TEST @Value(Language) = Special_Character
    FAILED -> AttributeCreator_3
    PASSED -> AttributeCreator_3
Note: Setting language to Farsi for Farsi characters
AttributeCreator_5
    ATTR_LIST = Language,Farsi
    -> AttributeCreator_3
Note: Concatenating all language values from all characters into one field
AttributeCreator_3
    ATTR_LIST = LanguageAll,@Value(LanguageAll) @Value(Language)
    -> AttributeCreator_4
Note: Concatenating all code values from all characters into one field
AttributeCreator_4
    ATTR_LIST = CodeAll,@Value(CodeAll) @Value(_code)
    -> Tester
Note: Tester to continue the loop until all characters / have been looked through
Tester
    BOOL_OP = OR
    TEST_DESCRIPTION = ""
    TEST_MODE = Automatic
    TEST_CLAUSE = NUM_TEST @Value(ContentCounter) < @Value(_length)
    PASSED -> AttributeCreator
    FAILED -> OUTPUT (output)
Note: Incrementing the counter to stop the loop if it hits the length of the content field
AttributeCreator
    ATTR_LIST = ContentCounter,@Evaluate(@Value(ContentCounter)+1)
    -> INPUT (output)
INPUT (output)
OUTPUT (output)

FME custom transformer f

INPUT (input)
OUTPUT (output)

FME custom transformer Histogram_List_Concatenator

INPUT (input)
    -> ListElementCounter
ListElementCounter
    CNT_ATTR = Histogram_count
    LIST_NAME = _histogram{}
    -> ListIndexer
ListIndexer
    LIST_ATTR = _histogram{}
    INDEX = @Value(Histogram_count)
    -> StringConcatenator
StringConcatenator
    PARM_LINE = @Value(value)@Value(count)
    VAL_ATTR = _concatenated2
    -> AttributeCreator
AttributeCreator
    ATTR_LIST = list_counter2,@Evaluate(@Value(list_counter2)+1)
    -> Tester_2
Tester_2
    BOOL_OP = OR
    TEST_DESCRIPTION = ""
    TEST_MODE = Automatic
    TEST_CLAUSE = TEST @Value(list_counter2) = @Value(Histogram_count)
    FAILED -> INPUT (output)
    PASSED -> OUTPUT (output)
    FAILED -> OUTPUT (output)
OUTPUT (output)
INPUT (output)
